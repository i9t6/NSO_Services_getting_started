module Srv_Policy_Map {
  namespace "http://example.com/Srv_Policy_Map";
  prefix Srv_Policy_Map;

  import ietf-inet-types {    prefix inet;  }
  import tailf-ncs {    prefix ncs;  }
  import tailf-common {    prefix tailf;  }

  augment /ncs:services {
    list Srv_Policy_Map {
      key policy_name;

      uses ncs:service-data;
      ncs:servicepoint Srv_Policy_Map-servicepoint;

      leaf policy_name {
        tailf:info "Service Policy Name";
        type string;
      }

      leaf cir {
              tailf:info "Set the CIR number, 1-4294967295";
              type uint32 { range 1..4294967295; }
      }
      leaf units {
              type enumeration {
                enum bps;
                enum gbps;
                enum kbps;
                enum mbps;
                enum pps;
              }
      }
      leaf cir_xe {
              tailf:info "Set the CIR number, 7-10,000,000,000";
              type uint64 { range 7..10000000000; }
      }
      leaf units_xe {
              type enumeration {
                enum bps;
                enum cps;
                enum pps;
              }
      }
      
      leaf-list device {
          tailf:info "Select a XR Device";
          type leafref {
            path "/ncs:devices/ncs:device/ncs:name";
          }
        }
      }
    }
  }
